CLAB-DEF-MIB DEFINITIONS ::= BEGIN
IMPORTS
	X509Certificate		FROM DOCS-BPI2-MIB
	MODULE-IDENTITY,
	enterprises			FROM SNMPv2-SMI;

cableLabs MODULE-IDENTITY
	LAST-UPDATED    "0209200000Z" -- September 20, 2002
    ORGANIZATION    "CableLabs"
    CONTACT-INFO
            "Ralph Brown
            Postal: Cable Television Laboratories, Inc.
			400 Centennial Parkway
			Louisville, Colorado 80027-1266
			U.S.A.
            Phone:  +1 303-661-9100
            Fax:    +1 303-661-9199
            E-mail: r.brown@cablelabs.com"
    DESCRIPTION
            "This MIB module supplies the basic management object categories for Cable 
Labs."
            
    ::= { enterprises 4491 }

clabFunction 		OBJECT IDENTIFIER ::= { cableLabs 1 }
clabFuncMib2 		OBJECT IDENTIFIER ::= { clabFunction 1 }
clabFuncProprietary OBJECT IDENTIFIER ::= { clabFunction 2 }
clabProject 		OBJECT IDENTIFIER ::= { cableLabs 2 }
clabProjDocsis 	OBJECT IDENTIFIER ::= { clabProject 1 }
clabProjPacketCable OBJECT IDENTIFIER ::= { clabProject 2 }
clabProjOpenCable	OBJECT IDENTIFIER ::= { clabProject 3}
clabProjCableHome   OBJECT IDENTIFIER ::= { clabProject 4 } 
clabSecurity 		OBJECT IDENTIFIER ::= { cableLabs 3}

clabSecCertObject OBJECT IDENTIFIER ::= { clabSecurity 1 }

clabSrvcPrvdrRootCACert 	OBJECT-TYPE
    SYNTAX 		X509Certificate
    MAX-ACCESS		read-only
    STATUS 		current
    DESCRIPTION
            "The X509 DER-encoded Service Provider Root CA Certificate."
    REFERENCE
    " Specification Section 11"
    ::= { clabSecCertObject 1 }

clabCVCRootCACert 		OBJECT-TYPE
    SYNTAX		X509Certificate
    MAX-ACCESS		read-only
    STATUS		current
    DESCRIPTION
            "The X509 DER-encoded CVC Root CA Certificate."
    REFERENCE
    " Specification Section 11 for Standalone PS Elements only"
    ::= { clabSecCertObject 2 }

clabCVCCACert 		OBJECT-TYPE
    SYNTAX		X509Certificate
    MAX-ACCESS		read-only
    STATUS		current
    DESCRIPTION
            "The X509 DER-encoded CableLabs CVC CA Certificate."
    REFERENCE
    " Specification Section 11 for Standalone PS Elements only"
    ::= { clabSecCertObject 3 }

clabMfgCVCCert 		OBJECT-TYPE
    SYNTAX		X509Certificate
    MAX-ACCESS		read-only
    STATUS		current
    DESCRIPTION
            "The X509 DER-encoded Manufacturer CVC Certificate."
    REFERENCE
    " Specification Section 11 for Standalone PS Elements only"
    ::= { clabSecCertObject 4 }

END
